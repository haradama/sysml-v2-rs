// A miniature ScalarValues, so the demo resolves without the corpus
// submodule. With the submodule checked out, pass the real library via
// `--library vendor/sysml-v2-release/sysml.library` instead.
package ScalarValues {
	abstract datatype Boolean;
	abstract datatype String;
	abstract datatype Real;
	abstract datatype Integer;
	abstract datatype Natural;
}
